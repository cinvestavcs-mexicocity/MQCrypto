MPKCKeys DEFINITIONS ::= BEGIN
    MPKCPublicKey ::= SEQUENCE {
        version  IA5String,
        key   OCTET STRING
    }

    MPKCPrivateKey ::= SEQUENCE {
    	version  IA5String,
        key   OCTET STRING
    }
END
